[DOCUMENT]
TITLE: spec-framework core requirements

[GRAMMAR]
ELEMENTS:
- TAG: REQUIREMENT
  FIELDS:
  - TITLE: UID
    TYPE: String
    REQUIRED: True
  - TITLE: TITLE
    TYPE: String
    REQUIRED: True
  - TITLE: STATUS
    TYPE: SingleChoice(Draft, Proposed, Approved, Deprecated)
    REQUIRED: True
  - TITLE: STATEMENT
    TYPE: String
    REQUIRED: True
  - TITLE: RATIONALE
    TYPE: String
    REQUIRED: False
  - TITLE: ACCEPTANCE
    TYPE: String
    REQUIRED: False
  - TITLE: COMPONENT
    TYPE: String
    REQUIRED: False
  - TITLE: CAPABILITY
    TYPE: String
    REQUIRED: False
  - TITLE: FORMAL
    TYPE: String
    REQUIRED: False
  - TITLE: CONTRACTS
    TYPE: String
    REQUIRED: False
  - TITLE: VERIFICATION
    TYPE: String
    REQUIRED: False
  - TITLE: EVIDENCE
    TYPE: String
    REQUIRED: False
  - TITLE: WAIVER
    TYPE: String
    REQUIRED: False
  - TITLE: REPLACES
    TYPE: String
    REQUIRED: False
  - TITLE: DECIDES
    TYPE: String
    REQUIRED: False
  - TITLE: QUESTIONS
    TYPE: String
    REQUIRED: False
  - TITLE: PROVENANCE
    TYPE: String
    REQUIRED: False
  - TITLE: OWNER
    TYPE: String
    REQUIRED: False
  - TITLE: PRIORITY
    TYPE: String
    REQUIRED: False

[REQUIREMENT]
UID: REQ-INIT-001
TITLE: Full-stack scaffold creation
STATUS: Draft
STATEMENT: When a project has no spec configuration, the spec CLI shall create the full-stack scaffold without modifying source files.
RATIONALE: Adoption must not rewrite the existing project.
ACCEPTANCE: AC-INIT-001
COMPONENT: CMP-SPEC-CLI
FORMAL: PROP-INIT-001
EVIDENCE: EVD-INIT-001
PROVENANCE: human:joao@2026-11-10
OWNER: spec-framework
PRIORITY: high

[REQUIREMENT]
UID: AC-INIT-001
TITLE: Scaffold contents
STATUS: Draft
STATEMENT: Given an empty project directory, the spec CLI creates spec/config.json and the requirement, architecture, formal, and contract directories.
FORMAL: PROP-INIT-001
EVIDENCE: EVD-INIT-001
PROVENANCE: human:joao@2026-11-10
OWNER: spec-framework

[REQUIREMENT]
UID: REQ-CHECK-001
TITLE: Structural error reporting
STATUS: Proposed
STATEMENT: When a requirement record contains a statement that does not match an EARS form, the spec CLI shall report a structural error with the source file and line.
RATIONALE: Gaps must be visible before native adapters run.
ACCEPTANCE: AC-CHECK-001
COMPONENT: CMP-SPEC-FRAMEWORK-CLI
FORMAL: PROP-CHECK-001
EVIDENCE: EVD-QUINT-CHECK-EVERYINVALIDRECORDREPORTED
PROVENANCE: human:joao@2026-11-10
OWNER: spec-framework
PRIORITY: high

[REQUIREMENT]
UID: AC-CHECK-001
TITLE: Non-EARS statement is rejected
STATUS: Proposed
STATEMENT: Given a requirement with a non-EARS statement, the spec CLI exits with status 1 and reports SDOC-BAD-EARS.
FORMAL: PROP-CHECK-001
EVIDENCE: EVD-QUINT-CHECK-EVERYINVALIDRECORDREPORTED
PROVENANCE: human:joao@2026-11-10
OWNER: spec-framework

[REQUIREMENT]
UID: REQ-DOCTOR-001
TITLE: Missing tool reporting
STATUS: Draft
STATEMENT: When a required native tool is missing, the spec CLI shall report the tool name and a provisioning command.
RATIONALE: Full-stack setup must be diagnosable in one step.
ACCEPTANCE: AC-DOCTOR-001
COMPONENT: CMP-SPEC-CLI
FORMAL: PROP-DOCTOR-001
EVIDENCE: EVD-DOCTOR-001
PROVENANCE: human:joao@2026-11-10
OWNER: spec-framework
PRIORITY: high

[REQUIREMENT]
UID: AC-DOCTOR-001
TITLE: Missing LikeC4 is reported
STATUS: Draft
STATEMENT: Given a missing LikeC4 executable, the spec CLI reports likec4 as missing and prints bun add -d likec4.
FORMAL: PROP-DOCTOR-001
EVIDENCE: EVD-DOCTOR-001
PROVENANCE: human:joao@2026-11-10
OWNER: spec-framework
